# TransitOps-M Station B v0.2 - FreeCAD 1.x macro (millimetres)
import FreeCAD as App
import os
N="TransitOps_M_Station_B"
if N in App.listDocuments():
 App.closeDocument(N)
d=App.newDocument(N)
colors={"base":(.72,.75,.77),"steel":(.25,.31,.35),"roof":(.16,.31,.40),"glass":(.41,.75,.85),"wood":(.57,.40,.25),"yellow":(.95,.76,.17),"blue":(.15,.34,.69),"dark":(.14,.17,.21)}
def group(n): return d.addObject("App::DocumentObjectGroup",n)
def box(g,n,l,w,h,x,y,z,color):
 o=d.addObject("Part::Box",n);o.Length=l;o.Width=w;o.Height=h
 o.Placement.Base=App.Vector(x,y,z);o.ViewObject.ShapeColor=colors[color];g.addObject(o);return o
def pole(g,n,r,h,x,y,z,color):
 o=d.addObject("Part::Cylinder",n);o.Radius=r;o.Height=h
 o.Placement.Base=App.Vector(x,y,z);o.ViewObject.ShapeColor=colors[color];g.addObject(o);return o
p=group("Platform")
box(p,"Platform_220x52x3",220,52,3,0,0,0,"base")
box(p,"Curb_Visual",220,2,1,0,0,3,"dark")
box(p,"Tactile_Edge_Visual",208,2.5,.5,6,3.8,3,"yellow")
s=group("Shelter")
X,Y=38,18
for i,(x,y) in enumerate(((X,Y),(X+132,Y),(X,Y+28),(X+132,Y+28)),1):
 pole(s,"Support_Post_%d"%i,1.5,33,x,y,3,"steel")
box(s,"Removable_Roof_Concept",144,35,2.2,X-6,Y-4,36,"roof")
box(s,"Rear_Glass_Placeholder",125,1.4,23,X+3.5,Y+26.6,11,"glass").ViewObject.Transparency=68
box(s,"Side_Glass_Placeholder",1.4,22,23,X+130.6,Y+2,11,"glass").ViewObject.Transparency=68
box(s,"Shelter_Header",144,1.8,3,X-6,Y-4,33.3,"steel")
f=group("Furniture")
for k,x in enumerate((X+20,X+80),1):
 box(f,"Bench_Seat_%d"%k,38,8,2,x,Y+13,13,"wood")
 box(f,"Bench_Back_%d"%k,38,2,12,x,Y+20,13,"wood")
 for j,xx in enumerate((x+5,x+30),1): box(f,"Bench_Leg_%d_%d"%(k,j),2,2,10,xx,Y+15,3,"steel")
box( 
 f, "Route_Map_Display",
 27, 1.8, 19,
 X + 53, Y + 26, 13,
 "blue"
)
sign=group("Signage_Ticketing")
pole(sign,"Stop_Pole",1.3,43,194,37,3,"steel")
box(sign,"Stop_Sign",11,2,13,188.5,36,33,"blue")
box(sign,"Ticket_Kiosk",11,9,25,8,32,3,"blue")
box(sign,"Kiosk_Screen",7,.6,8,10,31.4,17,"dark")
box(sign,"Route_Totem",10,5,32,204,31,3,"blue")
hw=group("Electronics_Placeholders")
box(hw,"Sensor_Enclosure",14,10,12,5,8,3,"dark")
box(hw,"Service_Conduit_Visual",140,3,1.2,35,46,3,"dark")
d.recompute()
Gui.activeDocument().activeView().viewAxonometric()
Gui.activeDocument().activeView().fitAll()
out=os.path.join(os.path.expanduser("~"),"Documents","TransitOps-M-CAD")
os.makedirs(out,exist_ok=True)
target=os.path.join(out,"TransitOps_M_Station_B.FCStd")
d.saveAs(target)
App.Console.PrintMessage("Station B saved to "+target+"\n")
